(defun c:konik ()
  (graphscr)
;;aci tanimlamasi: z1=0 z2=90 z3=180 z4=270
  (setq z1 0
        z2 (/ pi 2)
        z3 pi
        z4 (/(* 3 pi)2))
  (setq n1  (getpoint "\n Yerlesim noktasini seciniz:"))
  (setq a   (getreal  "\n Buyuk capi giriniz:"))
  (setq b   (getreal  "\n Kucuk capi giriniz:"))
  (setq h   (getreal  "\n Yuksekligi giriniz:"))
  (setq a1 (/ (- a b) 2))
  (setq b1 (/ b 2))
  (setq h1 (/ (* h b1) a1))
  (setq c  (sqrt(+(expt a1 2)(expt h 2))))
  (setq c1 (sqrt(+(expt b1 2)(expt h1 2))))
  (setq r  (+ c1 c))
  (setq aci (/(*(/(*(/ a 2)360) r)pi)180))
  (setq n3 (polar n1 z1 r))
  (setq n2 (polar n1 z1 c1))
  (setq n4 (polar n1 acý c1))
  (setq n5 (polar n1 acý r))  
  (command "line" n2 n3 "")
  (command "line" n4 n5 "")
  (command "arc" n2 "c" n1 n4 "")
  (command "arc" n3 "c" n1 n5 "")
  ;(setq arc1 (entnext))
  ;(setq arc2 (entnext arc1))
  ;(setq n4 (osnap arc1 "midp"))
  ;(setq n5 (osnap arc2 "midp"))
  ;(command "line" n4 n5 "") 
)
